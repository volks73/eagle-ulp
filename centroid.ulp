/*
 *  This EAGLE User Language Program creates the proper format
 *  Centroid file for assembly.
 */

string rotation(real Angle)
{
  string s;

  sprintf(s, "%.1f", Angle);
  for (int i = 0; s[i]; i++)
      if (s[i] == '.') {
         if (s[i + 1] == '0')
            s[i] = 0;
         break;
         }
   return s;
}

string side(int Mirror)
{
  string s;

  if (Mirror){
     s = "Bottom";
     }
     else {
     s = "Top";
     }
  return s;
}

if (board) board(B) {
   output(filesetext(B.name, "-centroid.csv")) {
     printf("%s,%s,%s,%s,%s\n", "RefDes", "Layer", "LocationX", "LocationY", "Rotation");
     B.elements(E) {
       printf("%s,%s,%5.3f,%5.3f,%s\n", E.name, side(E.mirror), u2inch(E.x), u2inch(E.y), rotation(E.angle));
     }
   }
}
