#usage "Creates a Shopping Cart for Upload to Digi-Key"
#require 7.00

int unique_parts_count = 0;
string descriptions[];
string manufacturers[];
string documentation_urls[];
string part_numbers[];
string supplier_urls[];
string supplier_names[];
string supplier_item_urls[];
string supplier_item_numbers[];
int quantities[];
int board_count = 5;

int result = dlgDialog("Board Quantity") {
    dlgHBoxLayout {
        dlgLabel("Number of Boards:");
        dlgIntEdit(board_count, 1, 2147483647);
    };
    dlgPushButton("-&DONE") {
        dlgAccept();
    };
};

board(B) {
    B.elements(E) {
        int is_duplicate = 0;
        for (int i = 0; i < unique_parts_count; i++) {
            if (part_numbers[i] == E.attribute["PART_NUMBER"] && E.attribute["PART_NUMBER"] != "") {
                is_duplicate = 1;
                break;
            }
        }
        if (is_duplicate) {
            quantities[i] = quantities[i] + 1;
        } else if (E.attribute["PART_NUMBER"] != "") {
            descriptions[i] = E.attribute["DESCRIPTION"];
            manufacturers[i] = E.attribute["MANUFACTURER"];
            documentation_urls[i] = E.attribute["DOCUMENTATION_URL"];
            part_numbers[i] = E.attribute["PART_NUMBER"];
            supplier_urls[i] = E.attribute["SUPPLIER_URL"];
            supplier_names[i] = E.attribute["SUPPLIER_NAME"];
            supplier_item_urls[i] = E.attribute["SUPPLIER_ITEM_URL"];
            supplier_item_numbers[i] = E.attribute["SUPPLIER_ITEM_NUMBER"];
            quantities[i] = 1;
            unique_parts_count = unique_parts_count + 1;
        }
    }
}

// Update quantities for number of boards to populate and extras to have on hand 
for (int i = 0; i < unique_parts_count; i++) {
    quantities[i] = quantities[i] * board_count;
    quantities[i] = quantities[i] + (5 - (quantities[i] % 5)); // Increase to the nearest 5 value
}

output("DigiKey-Shopping-Cart.csv", "wt") {
    for (int i = 0; i < unique_parts_count; i++) {
        printf("%u,%s\n", quantities[i], supplier_item_numbers[i]);
    }
}
