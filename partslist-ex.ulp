#usage "Creates a Parts List for a Board as a Text File"
#require 7.00

output("test.psv", "wt") {
    printf("| ID | DESCRIPTION | MANUFACTURER | PART NUMBER |\n");
    printf("|----|-------------|--------------|-------------|\n");
    board(B) {
        B.elements(E) {
            printf("| %s | %s | %s | %s |\n", E.name, E.attribute["DESCRIPTION"], E.attribute["MANUFACTURER"], E.attribute["PART_NUMBER"]);
        }
    }
}
